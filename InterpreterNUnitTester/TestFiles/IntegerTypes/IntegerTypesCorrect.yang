module IntegerTypesCorrect {
	yang-version 1;
	namespace
		"NamespaceCorrectTestModule1";

	prefix nctm;

	import yang-interpreter { prefix "yani"; }
	import interpreter-files { prefix "in-fi"; }
	import profiles { prefix "profiles"; }

	organization
		"My diplomwork corp";

	contact
		"Adam Sranko srankoadam@gmail.com";

	description 
		"Description of correctly formatted
		module,
		with multiline value.";

	reference
		"Reference1102-2323";

	revision 2039-09-11 {
		description "Generic Session 
		Control parameter file.";
	}

	leaf intTest1{
		type int8 {
			range "2..10";
		}
	}

	leaf intTest2{
		type int16;
	}

	leaf intTest3{
		type int32 {
			range "2..10";
		}
	}

	leaf intTest4{
		type int64;
	}


	leaf uintTest1{
		type uint8 {
			range "2..10";
		}
	}

	leaf uintTest2{
		type uint16;
	}

	leaf uintTest3{
		type uint32 {
			range "2..10";
		}
	}

	leaf uintTest4{
		type uint64;
	}
}
