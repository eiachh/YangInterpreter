module ArgumentParseTestInvalidCase {
	yang-version 1;
	namespace
		"NamespaceArgumentParseTestInvalidCase";

	prefix naptcc;

	leaf nonQuotedValid {
		description desc;
	}

	leaf singleQuotedValid {
		description 'desc';
	}

	leaf normalQuotedValid {
		description "desc";
	}

	leaf NormalQuoteConcatNormalQuoteValid {
		description "a" + "b";
	}

	leaf NormalQuoteConcatSingleQuoteValid {
		description "a"+'b';
	}

	leaf SingleQuoteConcatNormalQuoteValid {
		description 'a'+"b";
	}

	leaf SingleQuoteConcatSingleQuoteValid {
		description 'a'+'b';
	}

	leaf RecursiveLongRandomConcatValid {
		description 'a'+'b' + "c" +"d"+'e' +      "f"       +     "g";
	}

	leaf nonQuotedNextLineStartValid {
		description 
			desc;
	}

	leaf normalQuotedNextLineStartValid {
		description 
			"desc";
	}

	leaf singleQuotedNextLineStartValid {
		description 
			'desc';
	}

	leaf normalQuotedNextLineStartMultilineValid {
		description 
			"desc
			middle
			also desc";
	}

	leaf singleQuotedNextLineStartMultilineValid {
		description 
			'desc
			middle
			also desc';
	}

	leaf normalQuotedSameLineStartMultilineValid {
		description "desc
			middle
			middle2
			also desc";
	}

	leaf singleQuotedSameLineStartMultilineValid {
		description 'desc
			middle
			middle2
			also desc';
	}

	leaf normalQuotedSameLineStartMultilineConcattedValid {
		description "a"+"desc
			middle
			middle2
			also desc";
	}

	leaf singleQuotedSameLineConcattedStartMultilineValid {
		description 'a'+'desc
			middle
			middle2
			also desc';
	}

	leaf singleQuotedNextLineStartMultilineConcattedValid {
		description 
			'a'+'desc
			middle
			middle2
			also desc';
	}

	leaf normalQuotedNextLineStartMultilineConcattedValid {
		description 
			"a"+"desc
			middle
			middle2
			also desc";
	}

	leaf SpecialCharacterCheck {
		description 
			"a"+"de\{s;'c\"" + '"';
	}

	leaf MultilineConcatWithCompletedNormalQuotes {
		description "a" +
			+ "b" +
			"c";
	}

	leaf MultilineConcatWithCompletedSingleQuotes {
		description 'a' +
			+ 'b' +
			'c';
	}
	leaf statementAsText {
		description "module fakeStatement {";
	}
}
