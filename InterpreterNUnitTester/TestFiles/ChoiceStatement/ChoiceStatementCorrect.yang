module ChoiceStatementCorrect {
	yang-version 1;
	namespace
		"NamespaceGenericTestModule";

	prefix gtm;

	choice mainTester {
		anyxml "identifier" {
			config "false";
			description
				'the description';
			if-feature myFeature;
			mandatory "true";
			must "ifType != 'ethernet' or " 
			     + "(ifType = 'ethernet' and ifMTU = 1500)" {
					 error-message "An ethernet MTU must be 1500";
					 error-app-tag 'err app ta"g';
					 reference 'ref';
					 description " the description of this statement";
			}
			reference "the reference";
			status current;
			when 
				"xpath:xml:something/";
		}

		case case1;
		case case2;

		config "false";
		container someContainer { leaf leafOfContainer { type int8; } }
		default case1;
		description "desc";
		if-feature myFeature;
		leaf leafOfContainer { type int8; }

		leaf-list tester {

			config "true";

			description 'desc';
			if-feature myFeature;
			max-elements "+23";
			min-elements '0';
			must "ifType != 'ethernet'";
			ordered-by user;
			reference 'ref';
			status "current";
			type int32 {
				range "2..10";
			}
			units 
				"desc of unit";
			when 
				"xpath:xml:something/";
		}

		list listInList {
			config "true";
		}

		mandatory "true";
		reference "ref";
		status current;
		when arg;
	}
}
