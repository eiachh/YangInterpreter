module RangeStatementCorrect {
	yang-version 1;
	namespace
		"NamespaceCorrectTestModule1";

	prefix nctm;

	import yang-interpreter { prefix "yani"; }
	import interpreter-files { prefix "in-fi"; }
	import profiles { prefix "profiles"; }

	organization
		"My diplomwork corp";

	contact
		"Adam Sranko srankoadam@gmail.com";

	description 
		"Description of correctly formatted
		module,
		with multiline value.";

	reference
		"Reference1102-2323";

	revision 2039-09-11 {
		description "Generic Session 
		Control parameter file.";
	}
	leaf intTest{
		type int32 {
			range "2..10 
			| 51..343" {
				description 
					"description of 
					pattern.";
				error-app-tag "the error app tag";
				error-message "the error message";
				reference "the reference";
			}
		}
	}

	leaf decimalTest2{
		type decimal64 {
			range "3..11 | 52..344" {
				description "something";
			}
		}
	}
}
