module LeafListStatementCorrect {
	yang-version 1;
	namespace
		"NamespaceGenericTestModule";

	prefix gtm;

	leaf-list tester {

		config "true";

		description 'desc';
		if-feature myFeature;
		max-elements "+23";
		min-elements '0';
		must "ifType != 'ethernet'";
		ordered-by user;
		reference 'ref';
		status "current";
		type int32 {
			range "2..10";
		}
		units 
			"desc of unit";
		when 
			"xpath:xml:something/";
	}
}
